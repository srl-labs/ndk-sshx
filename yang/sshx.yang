module sshx {
  yang-version 1.1;
  namespace "urn:srlinux.dev:ndk:sshx";
  prefix ndk-sshx;

  import srl_nokia-common {
    prefix srl-comm;
  }

  description
    "sshx YANG module";

  revision 2024-10-04 {
    description
      "initial release";
  }

  container sshx {
    leaf admin-state {
      type srl-comm:admin-state;
      default "disable";
      description
        "Globally enable or disable the sshx.io tunnel

         Enabling the SSHX client will start the sshx binary and update the url value.";
    }
    leaf shell {
      type enumeration {
        enum cli {
          description
            "SR Linux CLI shell";
        }
        enum bash {
          description
            "Bash shell";
        }
      }
      description
        "The shell to use for the new windows in the SSHX web terminal";
      default "cli";
    }
    leaf url {
      description
        "URL of the SSHX.io web service";
      type string;
      config false;
    }
  }
}
